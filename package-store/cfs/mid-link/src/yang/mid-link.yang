module mid-link {
  namespace "http://com/example/mid-link";
  prefix mid-link;

  import ietf-inet-types {
    prefix inet;
  }

  import tailf-kicker { prefix kicker; }
  import tailf-common {
    prefix tailf;
  }
  import tailf-ncs {
    prefix ncs;
  }

  container actions {
    tailf:action notify {
      tailf:actionpoint notify;
      input {
        uses kicker:action-input-params;
      }
      output {
      }
    }
  }

  augment /ncs:services {
    list mid-link-data {
      config false;
      tailf:cdb-oper {
        tailf:persistent true;
      }
      key name;
      leaf name {
        type string;
      }
      list rfs-node {
        key name;
        leaf name {
          type leafref {
            path "/ncs:devices/ncs:device/ncs:name";
          }
        }
        leaf ready {
          type boolean;
          default false;
        }
      }
    }
    list mid-link {
      description "Mid link nano service";

      uses ncs:nano-plan-data;
      uses ncs:service-data;
      ncs:servicepoint mid-link-servicepoint;

      key name;
      leaf name {
        type string;
      }

      leaf unit {
        type uint32;
      }

      leaf vid {
        type uint32;
      }

      leaf iface {
        type string;
      }

      leaf sleep {
        type int32;
        default 0;
      }

      list rfs-node {
        key name;
        leaf name {
          type leafref {
            path "/ncs:devices/ncs:device/ncs:name";
          }
        }

        leaf sleep {
          type int32;
          default 0;
        }

        list devices {
          key name;
          leaf name {
            type string;
          }

          leaf list-entries {
            type int32;
            default 0;
          }
        }
      }
    }
  }

  identity vlan-link {
    base ncs:plan-component-type;
  }
  identity add-rfs-config {
    base ncs:plan-state;
  }

  ncs:plan-outline mid-link-plan {
   ncs:self-as-service-status;
    ncs:component-type "ncs:self" {
      ncs:state "ncs:init"{
        ncs:create {
          ncs:nano-callback;
        }
        ncs:delete {
          ncs:nano-callback;
        }
      }
      ncs:state "ncs:ready"{
        ncs:create {
          ncs:nano-callback;
        }
        ncs:delete {
          ncs:nano-callback;
        }
      }
    }

    ncs:component-type "mid-link:vlan-link" {
      ncs:state "ncs:init"{
        ncs:create {
          ncs:nano-callback;
        }
        ncs:delete {
          ncs:pre-condition {
            ncs:monitor "/ncs:services/mid-link:mid-link-data[name=$SNAME]" {
              ncs:trigger-expr "count(rfs-node[name=$RFSNAME]) = 0";
            }
          }
        }
      }
      ncs:state "mid-link:add-rfs-config"{
        ncs:create {
          ncs:nano-callback;
        }
      }
      ncs:state "ncs:ready" {
        ncs:create {
          ncs:pre-condition {
            ncs:monitor "/ncs:services/mid-link:mid-link-data[name=$SERVICE/name]/rfs-node[name=$RFSNAME]" {
              ncs:trigger-expr "ready = 'true'";
            }
          }
        }
      }
    }
  }

  ncs:service-behavior-tree mid-link-servicepoint {
    ncs:plan-outline-ref mid-link-plan;
    ncs:selector {
      ncs:create-component "'self'" {
        ncs:component-type-ref "ncs:self";
      }
      ncs:variable "SNAME" {
        ncs:value-expr "name";
      }
      ncs:multiplier {
        ncs:foreach "rfs-node" {
          ncs:variable "RFSNAME" {
            ncs:value-expr "name";
          }
          ncs:create-component "name" {
            ncs:component-type-ref "mid-link:vlan-link";
          }
        }
      }
    }
  }
}
